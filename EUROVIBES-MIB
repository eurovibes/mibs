EUROVIBES-MIB DEFINITIONS ::= BEGIN

IMPORTS
    MODULE-COMPLIANCE,
    OBJECT-GROUP
	FROM SNMPv2-CONF

    MODULE-IDENTITY,
    OBJECT-TYPE,
    enterprises
        FROM SNMPv2-SMI

    DisplayString
        FROM SNMPv2-TC;

eurovibes MODULE-IDENTITY
    LAST-UPDATED "201710121516Z"
    ORGANIZATION "EUROVIBES"
    CONTACT-INFO
	 "postal:   EUROVIBES
	 	    c/o Benedikt Spranger
                    Untere Weitfeldstr. 8
                    D-88690 Uhldingen-Muehlhofen

          email:    bene@eurovibes.org"
    DESCRIPTION
	"The management information base for the eurovibes projects."

    -- Revision block
    -- ff37f216a2bbd92e23b7ac086161f678abb1fa1b
    REVISION "201710121516Z"
    DESCRIPTION
    "release v0.1
    Signed-off-by: Benedikt Spranger <bene@eurovibes.org>
    "

    -- 21f4c6bc652def1f1690f24d440c003fb3776834
    REVISION "201710101634Z"
    DESCRIPTION
    "Initial version
    This repository contains the EUROVIBES MIB definitions.

    Signed-off-by: Benedikt Spranger <bene@eurovibes.org>
    "
    ::= { enterprises 50821 }

-- General objects

general OBJECT IDENTIFIER
    ::= { eurovibes 1 }

eurovibesGroups OBJECT IDENTIFIER
    ::= { eurovibes 2 }

eurovibesCompliances OBJECT IDENTIFIER
    ::= { eurovibes 3 }

eurovibesGeneralGroup OBJECT-GROUP
    OBJECTS { mibVersion }
    STATUS  current
    DESCRIPTION
            "EUROVIBES general MIB Group"
    ::= { eurovibesGroups 1 }

eurovibesCompliance MODULE-COMPLIANCE
    STATUS  current
    DESCRIPTION
           "The compliance statement for the EUROVIBES v1 entities which
           implement the EUROVIBES MIB."
      MODULE
      MANDATORY-GROUPS { eurovibesGeneralGroup }
::= { eurovibesCompliances 1 }

mibVersion OBJECT-TYPE
    SYNTAX DisplayString
    MAX-ACCESS read-only
    STATUS current
    DESCRIPTION
        "The MIB version that is used by the SNMP agent."
    ::= { general 1 }

END

-- https://creativecommons.org/licenses/by-nd/4.0/
-- Local Variables:
-- mode: snmpv2
-- End:
