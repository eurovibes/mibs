EUROVIBES-PROJECTS-MIB DEFINITIONS ::= BEGIN

IMPORTS
    MODULE-IDENTITY
	FROM SNMPv2-SMI
    eurovibes
        FROM EUROVIBES-MIB;

projects MODULE-IDENTITY
    LAST-UPDATED "201710121516Z"
    ORGANIZATION "EUROVIBES"
    CONTACT-INFO
	 "postal:   EUROVIBES
	 	    c/o Benedikt Spranger
                    Untere Weitfeldstr. 8
                    D-88690 Uhldingen-Muehlhofen

          email:    bene@eurovibes.org"
    DESCRIPTION
	"Definition of all eurovibes projects."

    -- Revision block
    -- ff37f216a2bbd92e23b7ac086161f678abb1fa1b
    REVISION "201710121516Z"
    DESCRIPTION
    "release v0.1
    Signed-off-by: Benedikt Spranger <bene@eurovibes.org>
    "

    -- 21f4c6bc652def1f1690f24d440c003fb3776834
    REVISION "201710101634Z"
    DESCRIPTION
    "Initial version
    This repository contains the EUROVIBES MIB definitions.

    Signed-off-by: Benedikt Spranger <bene@eurovibes.org>
    "
    ::= { eurovibes 2 }

END

-- https://creativecommons.org/licenses/by-nd/4.0/
-- Local Variables:
-- mode: snmpv2
-- End:
