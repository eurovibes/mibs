EUROVIBES-FBAGENT-MIB DEFINITIONS ::= BEGIN

IMPORTS
    MODULE-COMPLIANCE,
    OBJECT-GROUP
	FROM SNMPv2-CONF

    MODULE-IDENTITY,
    OBJECT-TYPE,
    Integer32,
    Unsigned32
	FROM SNMPv2-SMI

    projects
        FROM EUROVIBES-PROJECTS-MIB;

fbagent MODULE-IDENTITY
    LAST-UPDATED "201710121516Z"
    ORGANIZATION "EUROVIBES"
    CONTACT-INFO
	 "postal:   EUROVIBES
	 	    c/o Benedikt Spranger
                    Untere Weitfeldstr. 8
                    D-88690 Uhldingen-Muehlhofen

          email:    bene@eurovibes.org"
    DESCRIPTION
	"Definition of all eurovibes projects."

    -- Revision block
    -- ff37f216a2bbd92e23b7ac086161f678abb1fa1b
    REVISION "201710121516Z"
    DESCRIPTION
    "release v0.1
    Signed-off-by: Benedikt Spranger <bene@eurovibes.org>
    "

    -- 21f4c6bc652def1f1690f24d440c003fb3776834
    REVISION "201710101634Z"
    DESCRIPTION
    "Initial version
    This repository contains the EUROVIBES MIB definitions.

    Signed-off-by: Benedikt Spranger <bene@eurovibes.org>
    "
    ::= { projects 1 }

fbagentVars OBJECT IDENTIFIER
    ::= { fbagent 1 }

fbagentGroups OBJECT IDENTIFIER
    ::= { fbagent 2 }

fbagentCompliances OBJECT IDENTIFIER
    ::= { fbagent 3 }

fbagentGroup OBJECT-GROUP
    OBJECTS {
    fbagentBoxUDN,
    fbagentBoxName,
    fbagentBoxUpstreamMaxBitRate,
    fbagentBoxDownstreamMaxBitRate,
    fbagentPhysicalLinkStatus
    }
    STATUS  current
    DESCRIPTION
            "fbagent object group"
    ::= { fbagentGroups 2 }

fbagentCompliance MODULE-COMPLIANCE
    STATUS  current
    DESCRIPTION
           "The compliance statement for the fbagent v1 entities which
           implement the fbagent MIB."
      MODULE
      MANDATORY-GROUPS { fbagentGroup }
::= { fbagentCompliances 1 }

-- fbagent box table

fbagentBoxTable OBJECT-TYPE
    SYNTAX	SEQUENCE OF FBAGENTBOXENTRY
    MAX-ACCESS	not-accessible
    STATUS      current
    DESCRIPTION
	"Table of identified router boxes."

    ::= { fbagentVars 1 }

fbagentBoxEntry OBJECT-TYPE
    SYNTAX	FBAGENTBOXENTRY
    MAX-ACCESS	not-accessible
    STATUS      current
    DESCRIPTION
	" "
    INDEX	{ fbagentBoxIndex }
    ::= { fbagentBoxTable 1 }

FBAGENTBOXENTRY ::= SEQUENCE {
fbagentBoxIndex			Unsigned32,
fbagentBoxUDN			OCTET STRING,
fbagentBoxName			OCTET STRING,
fbagentBoxUpstreamMaxBitRate	Integer32,
fbagentBoxDownstreamMaxBitRate	Integer32,
fbagentPhysicalLinkStatus	Integer32
}

fbagentBoxIndex OBJECT-TYPE
    SYNTAX      Unsigned32
    MAX-ACCESS  not-accessible
    STATUS      current
    DESCRIPTION
        " "
    ::= { fbagentBoxEntry 1 }

fbagentBoxUDN OBJECT-TYPE
    SYNTAX	OCTET STRING
    MAX-ACCESS	read-only
    STATUS	current
    DESCRIPTION
	" "
    ::= { fbagentBoxEntry 2 }

fbagentBoxName	OBJECT-TYPE
    SYNTAX	OCTET STRING
    MAX-ACCESS	read-only
    STATUS	current
    DESCRIPTION
        " "
    ::= { fbagentBoxEntry 3 }

fbagentBoxUpstreamMaxBitRate OBJECT-TYPE
    SYNTAX      Integer32
    MAX-ACCESS  read-only
    STATUS      current
    DESCRIPTION
        " "
    DEFVAL { 0 }
    ::= { fbagentBoxEntry 4 }

fbagentBoxDownstreamMaxBitRate OBJECT-TYPE
    SYNTAX      Integer32
    MAX-ACCESS  read-only
    STATUS      current
    DESCRIPTION
        " "
    DEFVAL { 0 }
    ::= { fbagentBoxEntry 5 }

fbagentPhysicalLinkStatus OBJECT-TYPE
    SYNTAX	INTEGER {
    			up(1),
			down(2),
			iniitializing(3),
			unavailable(4)
		}
    MAX-ACCESS	read-only
    STATUS	current
    DESCRIPTION
        " "
    ::= { fbagentBoxEntry 6 }

END
-- Local Variables:
-- mode: snmpv2
-- End:
